module ace-audit {
  yang-version 1.1;
  namespace "urn:ace:net:audit";
  prefix "audit";

  import ietf-yang-types {
    prefix yang;
  }

  // In a real implementation, this would import the ace-policy module
  // to get direct access to the typedefs.
  // import ace-policy { prefix policy; }

  // For this example, we define local typedefs for policy/rule references.
  typedef policy-id-ref {
    type string;
    description
      "A reference to a policy identifier, as defined in ace-policy.yang.";
  }
  typedef rule-id-ref {
    type string;
    description
      "A reference to a rule identifier, as defined in ace-policy.yang.";
  }

  description
    "This YANG data model defines the structure for machine-readable
     audit logs and compliance reports within the ACE-NET framework.
     It provides a comprehensive schema for capturing event-level audit
     trails and aggregated compliance reporting data.";

  revision 2024-05-21 {
    description "Initial version.";
    reference "draft-doe-ace-net-framework-00";
  }

  grouping event-metadata {
    description "Common metadata for all logged events.";
    leaf timestamp {
      type yang:date-and-time;
      mandatory true;
      description "The exact time the event occurred.";
    }
    leaf correlation-id {
      type yang:uuid;
      description
        "A unique identifier to correlate related events across
         different systems or components.";
    }
  }

  container audit-data {
    description "Root container for all audit and compliance data.";

    list audit-trail {
      key "event-id";
      description
        "A chronological log of security-relevant events, forming
         a complete audit trail.";

      leaf event-id {
        type yang:uuid;
        description "A unique identifier for this audit event.";
      }

      container event-source {
        description "Information about the source of the event.";
        leaf component-id {
          type string;
          description "The identifier of the component that generated the event (e.g., agent ID, node name).";
        }
        leaf component-type {
          type enumeration {
            enum agent;
            enum controller;
            enum orchestrator;
            enum other;
          }
          description "The type of the component.";
        }
        leaf source-ip {
          type string; // Could be ietf:ip-address if imported
          description "The IP address of the event source.";
        }
      }

      leaf event-type {
        type string;
        mandatory true;
        description "A high-level description of the event type (e.g., 'PolicyEvaluation', 'RemediationAction').";
      }

      container policy-references {
        description "References to the policy and rule that this event relates to.";
        leaf policy-id {
          type policy-id-ref;
        }
        leaf rule-id {
          type rule-id-ref;
        }
      }

      leaf event-details {
        type string;
        description "A human-readable description or JSON blob with detailed event data.";
      }
      
      uses event-metadata;
    }

    list compliance-reports {
      key "report-id";
      description
        "A collection of compliance reports generated by the system.";

      leaf report-id {
        type yang:uuid;
        mandatory true;
        description "A unique identifier for the compliance report.";
      }

      uses event-metadata; // For report generation timestamp

      container summary {
        description "A high-level summary of the compliance report.";
        leaf overall-status {
          type enumeration {
            enum pass;
            enum fail;
            enum warning;
            enum indeterminate;
          }
          mandatory true;
          description "The overall compliance status determined by this report.";
        }
        leaf total-rules-evaluated {
          type uint32;
        }
        leaf rules-passed {
          type uint32;
        }
        leaf rules-failed {
          type uint32;
        }
        leaf score {
          type uint8 {
            range "0 .. 100";
          }
          description "A numeric compliance score, e.g., percentage of rules passed.";
        }
      }

      list test-suite-results {
          key "suite-id";
          description "Breakdown of results by test suite.";
          
          leaf suite-id {
              type string;
          }
          leaf status {
              type enumeration {
                enum pass;
                enum fail;
              }
          }
          leaf test-cases-passed {
              type uint32;
          }
          leaf test-cases-failed {
              type uint32;
          }
      }

      list rule-evaluation-results {
        key "result-id";
        description
          "A detailed list of individual rule evaluation outcomes.";

        leaf result-id {
          type string; // e.g., a combination of policy-id and rule-id
          description "A unique ID for this specific rule result.";
        }
        
        leaf policy-id {
          type policy-id-ref;
          mandatory true;
        }

        leaf rule-id {
          type rule-id-ref;
          mandatory true;
        }

        leaf status {
          type enumeration {
            enum pass;
            enum fail;
            enum not-applicable;
            enum error;
          }
          mandatory true;
          description "The pass/fail status of the rule evaluation.";
        }

        leaf observed-value {
          type string;
          description "The actual value observed during the evaluation.";
        }

        leaf expected-value {
          type string;
          description "The expected value as defined by the policy rule.";
        }

        leaf message {
          type string;
          description "Additional details or context about the evaluation result.";
        }
      }

      list evidence-references {
        key "evidence-id";
        description "A list of references to captured evidence.";
        leaf evidence-id {
          type string;
        }
        leaf evidence-uri {
          type string; // Could be ietf:uri if imported
          description "A URI pointing to the stored evidence file or data.";
        }
        leaf description {
          type string;
        }
      }

      list remediation-actions {
        key "action-id";
        description "A list of remediation actions that were triggered as a result of this report.";
        leaf action-id {
          type yang:uuid;
        }
        leaf action-type {
          type string;
          description "e.g., 'BlockPort', 'IsolateHost', 'ReconfigureService'.";
        }
        leaf status {
          type enumeration {
            enum triggered;
            enum completed;
            enum failed;
          }
        }
        leaf timestamp {
          type yang:date-and-time;
        }
        leaf details {
          type string;
        }
      }
    }
  }
}
