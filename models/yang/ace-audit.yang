module ace-audit {
  yang-version 1.1;
  namespace "urn:ace-net:yang:ace-audit";
  prefix audit;

  import ietf-yang-types { prefix yang; }

  description
    "ACE-NET three-layer audit trail and compliance report schema.
     Instances of this model are assembled by the Evidence Store (Phase 3)
     and serialized as the CertificationReport payload.";

  revision 2026-06-29 {
    description "v2.0 — three-layer model aligned to ACE Phase 0-3 pipeline.";
    reference "draft-doe-ace-net-framework-00";
  }

  container certification-report {
    leaf report-id      { type yang:uuid; mandatory true; }
    leaf agent-id       { type string; mandatory true; }
    leaf agent-version  { type string; mandatory true; }
    leaf issued-at      { type yang:date-and-time; mandatory true; }
    leaf issued-by      { type string; default "ACE-NET-CA"; }

    leaf autonomy-level-claimed { type string; mandatory true; }
    leaf autonomy-level-achieved { type string; mandatory true;
      description "Computed by ACE-NET from Layer 3 results. MUST NOT be set by the agent provider."; }

    container layer1 {
      description "Phase 0-2 pipeline output for isolated behavioral certification.";
      leaf behavioral-score      { type decimal64 { fraction-digits 2; } mandatory true; }
      leaf rules-evaluated       { type uint32; mandatory true; }
      leaf rules-passed          { type uint32; mandatory true; }
      leaf tmf-api-conformance   { type enumeration { enum PASS; enum FAIL; } mandatory true; }
      leaf ttd-p95-seconds       { type decimal64 { fraction-digits 2; }
        description "95th percentile Time to Detect across all fault injections."; }
      leaf ttr-p95-seconds       { type decimal64 { fraction-digits 2; }
        description "95th percentile Time to Remediate across all fault injections."; }
      leaf tool-call-accuracy    { type decimal64 { fraction-digits 2; }
        description "Fraction of TMF API calls with correct schema and semantics (0.0–1.0)."; }
    }

    container layer2 {
      description "A2A-T protocol conformance results. Present only when min-tier >= 3.";
      leaf ig1453-version        { type string; }
      leaf agent-card-valid      { type boolean; }
      leaf task-lifecycle        { type enumeration { enum PASS; enum FAIL; enum NOT_RUN; } }
      leaf multi-agent-flow      { type enumeration { enum PASS; enum FAIL; enum NOT_RUN; } }
      leaf error-handling        { type enumeration { enum PASS; enum FAIL; enum NOT_RUN; } }
      leaf prompt-meta-model     { type enumeration { enum PASS; enum FAIL; enum NOT_RUN; } }
      leaf fabric-faults-passed  { type uint8;
        description "Number of fabric fault scenarios passed (max 4 per Layer 2 run)."; }
    }

    list layer3-hvs-result {
      key hvs-id;
      description "Per-HVS scenario results. One entry per scenario in scenario_profile_ids.";
      leaf hvs-id                { type string; mandatory true; }
      leaf status                { type enumeration { enum PASS; enum FAIL; enum NOT_RUN; } mandatory true; }
      leaf elapsed-seconds       { type uint32; }
      leaf sla-seconds           { type uint32;
        description "Declared SLA threshold for this scenario."; }
      leaf intent-fulfilled      { type boolean; }
      leaf failure-reason        { type string;
        description "Present only when status is FAIL."; }
    }

    leaf intent-fulfillment-rate { type decimal64 { fraction-digits 2; }
      description "Fraction of Layer 3 HVS scenarios where intent was fulfilled (0.0–1.0)."; }

    leaf certificate-jwt         { type string;
      description "The signed JWT Compliance Certificate payload (JWS compact serialization)."; }
  }
}
