module ace-policy {
  yang-version 1.1;
  namespace "urn:ace-net:yang:ace-policy";
  prefix acep;

  import ietf-inet-types { prefix inet; }
  import ietf-yang-types { prefix yang; }

  organization "ACE-NET / AgentCert Initiative";
  contact "Editor: <mailto:editor@ace-net.example.com>";
  description
    "YANG module for ACE-NET compliance policies. Defines rules,
     thresholds, ECA definitions, and autonomy-level constraints
     evaluated against AUT behavior during Layer 1 certification.";

  revision 2026-06-29 {
    description "v2.0 — added telecom domain typedefs and A2A-T rule types.";
    reference "draft-doe-ace-net-framework-00";
  }

  typedef autonomy-level {
    type enumeration {
      enum L0 { description "Manual — no autonomous action."; }
      enum L1 { description "Assisted — human approves every action."; }
      enum L2 { description "Partial Self-X — bounded single task."; }
      enum L3 { description "Conditional Self-X — single-domain autonomous."; }
      enum L4 { description "High Self-X — cross-domain intent-driven."; }
    }
    description "TMForum IG1218 autonomy level.";
  }

  typedef cert-tier {
    type uint8 { range "0..4"; }
    description "ACE-NET certification tier (0=interface, 1=behavioral, 2=playbook, 3=a2at, 4=fabric+hvs).";
  }

  typedef hvs-scenario-id {
    type enumeration {
      enum HVS-1 { description "Autonomous Fault Management."; }
      enum HVS-2 { description "Zero-Touch Network Slicing."; }
      enum HVS-3 { description "Self-Optimizing RAN."; }
      enum HVS-4 { description "Proactive SLA Assurance."; }
      enum HVS-5 { description "Complaint Handling (A2A-T reference scenario)."; }
    }
    description "High-Value Scenario identifier per Section 8.";
  }

  typedef tmf-api-id {
    type enumeration {
      enum TMF628; enum TMF639; enum TMF640;
      enum TMF641; enum TMF654; enum TMF688; enum TMF724;
    }
    description "TMForum Open API identifier.";
  }

  container policy {
    leaf policy-id    { type yang:uuid; mandatory true; }
    leaf name         { type string; mandatory true; }
    leaf min-tier     { type cert-tier; default 1; }
    leaf max-tier     { type cert-tier; default 4; }
    leaf behavioral-score-threshold { type decimal64 { fraction-digits 1; }
      default "80.0";
      description "Minimum Layer 1 behavioral score to pass (0.0–100.0)."; }
    leaf behavioral-score-drift-margin { type decimal64 { fraction-digits 1; }
      default "10.0";
      description "Max behavioral score drift before continuous-monitoring re-cert triggers."; }

    list rule {
      key rule-id;
      leaf rule-id    { type yang:uuid; mandatory true; }
      leaf name       { type string; mandatory true; }
      leaf type       { type enumeration {
        enum metric-based-threshold;
        enum state-assertion;
        enum api-call-sequence-validation;
        enum eca-decision-correctness;
        enum a2at-protocol-assertion;
      }; mandatory true; }
      leaf severity   { type enumeration { enum critical; enum major; enum minor; }; default major; }
      leaf description { type string; }
    }

    list eca-definition {
      key eca-id;
      description "Event-Condition-Action definition for autonomous remediation validation.";
      leaf eca-id     { type yang:uuid; mandatory true; }
      leaf event-type { type string; mandatory true; }
      leaf condition  { type string; description "XPath expression evaluated against network state."; }
      leaf expected-action { type string; description "Expected agent action within declared boundaries."; }
      leaf timeout-seconds { type uint32; default 300; }
    }
  }
}
